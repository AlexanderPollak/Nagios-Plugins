-- *****************************************************************
-- Moxa Active Ethernet I/O Server MIB
--
-- 01-03-2013
--
-- Copyright (c) 2013 by Moxa Automation Co., Ltd.
-- All rights reserved.
-- *****************************************************************

MOXA-IO-E1242-MIB DEFINITIONS ::= BEGIN
    IMPORTS
        enterprises, Unsigned32, Integer32, MODULE-IDENTITY, OBJECT-TYPE, NOTIFICATION-TYPE FROM SNMPv2-SMI;
   
-- 1.3.6.1.4.1.8691.10.1242
    e1242   MODULE-IDENTITY
    LAST-UPDATED "201609061100Z"
    ORGANIZATION "Moxa Automation,Inc."
    CONTACT-INFO
            "Postal: Moxa Automation,Inc.
             Fl.4, No.135,Lane 235,Pao-Chiao Rd.
             Shing Tien City,Taipei,Taiwan,R.O.C
             Tel: +866-2-89191230 "
    DESCRIPTION
            "The MIB module for Moxa ioLogik Remote Ethernet I/O specific information." 
		
	REVISION "201609061100Z"      
	DESCRIPTION
            "fix typo (dioPulsONWidth -> dioPulseONWidth, dioPulsOFFWidth -> dioPulseOFFWidth)"			
				
	REVISION "201607281400Z"      
	DESCRIPTION
            "rename description of trap item and add item of counter_overflow_clear"
			
	REVISION "201604061300Z"      
	DESCRIPTION
            "rename description of each item"
	
	REVISION "201601140900Z"      
	DESCRIPTION
            "remove di type entry"   
			
	REVISION "201601041300Z"      
	DESCRIPTION
            "Validate level 3 of simple web"   
	REVISION "201512041600Z" 
    DESCRIPTION
            "First version of this MIB."
    REVISION "201302211400Z"   
    DESCRIPTION
            "The Trap Support SNMPv2" 
                        
           ::= { ioLogik 1242 }    -- 1.3.6.1.4.1.8691.10.1242

-- 1.3.6.1.4.1.8691
    moxa OBJECT IDENTIFIER ::= { enterprises 8691 }

-- 1.3.6.1.4.1.8691.10
    ioLogik OBJECT IDENTIFIER ::= { moxa 10 }

-- 1.3.6.1.4.1.8691.10.1242.1
    totalChannelNumber OBJECT-TYPE
        SYNTAX Integer32 (1..16)
        MAX-ACCESS read-only
        STATUS current
        DESCRIPTION
            "Total I/O channels."
        ::= { e1242 1 }

-- 1.3.6.1.4.1.8691.10.1242.2
    serverModel OBJECT-TYPE
        SYNTAX OCTET STRING
        MAX-ACCESS read-only
        STATUS current
        DESCRIPTION
            "The I/O server model."
        ::= { e1242 2 }

-- 1.3.6.1.4.1.8691.10.1242.3
    systemTime OBJECT-TYPE
        SYNTAX Integer32
        MAX-ACCESS read-only
        STATUS current
        DESCRIPTION
            "I/O server up time (in seconds)."
        ::= { e1242 3 }

-- 1.3.6.1.4.1.8691.10.1242.4
    firmwareVersion OBJECT-TYPE
        SYNTAX OCTET STRING
        MAX-ACCESS read-only
        STATUS current
        DESCRIPTION
            "The firmware version."
        ::= { e1242 4 }


----------------------------------------------------------------
-- I/O
-- 1.3.6.1.4.1.8691.10.1242.10          
    e1242monitor OBJECT IDENTIFIER ::= { e1242 10 }
----------------------------------------------------------------
-- DI channel
diTable OBJECT-TYPE
        SYNTAX          SEQUENCE OF DIEntry
        MAX-ACCESS      not-accessible
        STATUS          current
        DESCRIPTION     
            "The DI channel monitor table"
        ::= { e1242monitor 1 }

diEntry OBJECT-TYPE
        SYNTAX          DIEntry
        MAX-ACCESS      not-accessible
        STATUS          current
        DESCRIPTION     
            "The DI channel monitor item"
        INDEX { diIndex }
        ::= { diTable 1 }

DIEntry ::= SEQUENCE {
                diIndex     Integer32,
                diMode      Integer32,
                diStatus    Integer32,
                diFilter    Integer32,
                diTrigger   Integer32,
                diCntStart  Integer32,
				diCounterReset Integer32,
				diCounterOverflowFlag Integer32,
				diCounterOverflowFlagClear Integer32				
                 }

diIndex OBJECT-TYPE
        SYNTAX          Integer32  (0..7)
        MAX-ACCESS      read-only
        STATUS          current
        DESCRIPTION     
            "DI - index"
        ::= { diEntry 1 }   
        
diMode OBJECT-TYPE
        SYNTAX          Integer32  (0..1)
        MAX-ACCESS      read-write
        STATUS          current
        DESCRIPTION     "DI - mode (0: DI, 1: Counter mode)"
        ::= { diEntry 3 }
 
diStatus OBJECT-TYPE
        SYNTAX          Integer32 (0..2147483647)
        MAX-ACCESS      read-only
        STATUS          current
        DESCRIPTION     "DI - DI mode status (0: OFF, 1: ON) or Counter mode value"
        ::= { diEntry 4 }
        
diFilter OBJECT-TYPE
        SYNTAX          Integer32  (1..65535)
        MAX-ACCESS      read-write
        STATUS          current
        DESCRIPTION     "DI - filter setting (unit: 1 ms)"
        ::= { diEntry 5 }

diTrigger OBJECT-TYPE
        SYNTAX          Integer32  (0..2)
        MAX-ACCESS      read-write
        STATUS          current
        DESCRIPTION     "DI - Counter mode - event (0: Rising Edge, 1: Falling Edge, 2: Both)"
        ::= { diEntry 6 }

diCntStart OBJECT-TYPE
        SYNTAX          Integer32 (0..1)
        MAX-ACCESS      read-write
        STATUS          current
        DESCRIPTION     "DI - Counter mode - status (0: STOP, 1: START)"
        ::= { diEntry 7 }

diCounterReset OBJECT-TYPE
        SYNTAX          Integer32 (0..1)
        MAX-ACCESS      read-write
        STATUS          current
        DESCRIPTION     "DI - Counter mode - reset to initial value (1: RESET)"
        ::= { diEntry 8 }		
	
diCounterOverflowFlag OBJECT-TYPE
        SYNTAX          Integer32 (0..1)
        MAX-ACCESS      read-only
        STATUS          current
        DESCRIPTION     "DI - Counter mode - overflow flag (0: Normal, 1: Overflow)"
        ::= { diEntry 9 }		

diCounterOverflowFlagClear OBJECT-TYPE
        SYNTAX          Integer32 (0..1)
        MAX-ACCESS      read-write
        STATUS          current
        DESCRIPTION     "DI - Counter mode - clear overflow flag (1:CLEAR)"
        ::= { diEntry 10 }		
----------------------------------------------------------------
---------------------------------------------------------------- 
-- DIO channel
dioTable OBJECT-TYPE
		SYNTAX 			SEQUENCE OF DIOEntry
		MAX-ACCESS 		not-accessible
		STATUS 			current
		DESCRIPTION		"The DIO channel monitor table"
		::= { e1242monitor 3 }

dioEntry OBJECT-TYPE
		SYNTAX 			DIOEntry
		MAX-ACCESS 		not-accessible
		STATUS 			current
		DESCRIPTION		"The DIO channel monitor item"
		INDEX { dioIndex }
		::= { dioTable 1 }

DIOEntry ::= SEQUENCE { 
        dioIndex		Integer32,
		dioType			Integer32,
		dioMode			Integer32,
		dioStatus		Integer32,
		dioDIFilter		Integer32,
		dioDITrigger        Integer32,
		dioDICntStart    	Integer32,
		dioDOPulseONWidth   	Integer32,
		dioDOPulseOFFWidth  	Integer32,
   		dioDOPulseStart	    Integer32,
		dioDICounterReset		Integer32,
		dioDICounterOverflowFlag  Integer32,
		dioDICounterOverflowFlagClear Integer32		
		}                       
			
dioIndex OBJECT-TYPE
		SYNTAX 			Integer32(0..7)
		MAX-ACCESS 		read-only
		STATUS 			current
		DESCRIPTION		"DIO - index"
		::= { dioEntry 1}

dioType OBJECT-TYPE
		SYNTAX 			Integer32(0..1)
		MAX-ACCESS 		read-only
		STATUS 			current
		DESCRIPTION		"DIO - mode (0: DI, 1: DO)"
		::= { dioEntry 2 }
		
dioMode OBJECT-TYPE
		SYNTAX 			Integer32(0..1)
		MAX-ACCESS 		read-write
		STATUS 			current
		DESCRIPTION		"DIO - DI mode (0: DI, 1: Counter mode); DO - mode (0: DO, 1: Pulse)"
		::= { dioEntry 3 }
		
dioStatus OBJECT-TYPE
		SYNTAX 			Integer32(0..2147483647) 
		MAX-ACCESS 		read-write
		STATUS 			current
		DESCRIPTION		"DIO - DI mode status (0: OFF, 1: ON), Counter mode value, DO status (0: OFF, 1: ON), or Pulse count"
		::= { dioEntry 4 }
		
dioDIFilter OBJECT-TYPE
		SYNTAX 			Integer32(1..65535)
		MAX-ACCESS 		read-write
		STATUS 			current
		DESCRIPTION		"DIO - DI mode - filter setting (unit: 1 ms)"
		::= { dioEntry 5 }

dioDITrigger OBJECT-TYPE
		SYNTAX 			Integer32(0..2)
		MAX-ACCESS 		read-write
		STATUS 			current
		DESCRIPTION		"DIO - DI mode - Counter mode - event (0: Rising Edge, 1: Falling Edge, 2: Both)"
		::= { dioEntry 6 } 

dioDICntStart OBJECT-TYPE
		SYNTAX 			Integer32(0..1)
		MAX-ACCESS 		read-write
		STATUS 			current
		DESCRIPTION		"DIO - DI mode - Counter mode - status (0: STOP, 1: START)"
		::= { dioEntry 7 }


dioDOPulseONWidth 	OBJECT-TYPE
		SYNTAX 			Integer32(1..65535)
		MAX-ACCESS 		read-write
		STATUS 			current
		DESCRIPTION		"DIO - DO mode - Pulse mode - ON width (unit: 1 ms)"
		::= { dioEntry 8 }
		
dioDOPulseOFFWidth	OBJECT-TYPE
		SYNTAX 			Integer32(1..65535)
		MAX-ACCESS 		read-write
		STATUS 			current
		DESCRIPTION		"DIO - DO mode - Pulse mode - OFF width (unit: 1 ms)"
		::= { dioEntry 9}


dioDOPulseStart OBJECT-TYPE
		SYNTAX 			Integer32(0..1)
		MAX-ACCESS 		read-write
		STATUS 			current
		DESCRIPTION		"DIO - DO mode - Pulse mode - status (0: STOP, 1: START)"
		::= { dioEntry 10}

dioDICounterReset OBJECT-TYPE
		SYNTAX 			Integer32 (0..1)
		MAX-ACCESS 		read-write
		STATUS 			current
		DESCRIPTION		"DIO - DI mode - Counter mode - reset to initial value (1: RESET)"
		::= { dioEntry 11}
	 

dioDICounterOverflowFlag OBJECT-TYPE
		SYNTAX 			Integer32 (0..1)
		MAX-ACCESS 		read-only
		STATUS 			current
		DESCRIPTION		"DIO - DI mode - Counter mode - overflow flag (0: Normal, 1: Overflow)"
		::= { dioEntry 12}	 	

dioDICounterOverflowFlagClear OBJECT-TYPE
		SYNTAX 			Integer32 (0..1)
		MAX-ACCESS 		read-write
		STATUS 			current
		DESCRIPTION		"DIO - DI mode - Counter mode - clear overflow flag (1:CLEAR)"
		::= { dioEntry 13}			
----------------------------------------------------------------
---------------------------------------------------------------- 
-- ai
aiTable OBJECT-TYPE
		SYNTAX 			SEQUENCE OF AIEntry
		MAX-ACCESS 		not-accessible
		STATUS 			current
		DESCRIPTION		"The ai channel monitor table"
		::= { e1242monitor 4 }

aiEntry OBJECT-TYPE
		SYNTAX			AIEntry
		MAX-ACCESS 		not-accessible
		STATUS 			current
		DESCRIPTION		"The ai channel monitor item"
		INDEX { aiIndex }
		::= { aiTable 1 }

AIEntry ::=	SEQUENCE {
		aiIndex		Integer32,
		aiEnable	Integer32, 
		aiMode 		Integer32,
		aiValue		Integer32,
		aiMin		Integer32,
		aiMax		Integer32,
		aiValueScaled	OCTET STRING,
		aiValueScaledMin	OCTET STRING,
		aiValueScaledMax	OCTET STRING,
		aiResetMinValue		Integer32,
		aiResetMaxValue		Integer32,
		aiStatus		Integer32,
		aiBurnoutValue	OCTET STRING	
}
-------------------------------------------
aiIndex OBJECT-TYPE
		SYNTAX 			Integer32(0..3)
		MAX-ACCESS 		read-only
		STATUS 			current
		DESCRIPTION		"AI - index"
		::= { aiEntry 1 }
aiEnable OBJECT-TYPE
		SYNTAX 			Integer32(0..1)
		MAX-ACCESS 		read-write
		STATUS 			current
		DESCRIPTION		"AI - function (0: Disable, 1: Enable)"
		::= { aiEntry 2 }

aiMode OBJECT-TYPE
		SYNTAX 			Integer32(0..4)
		MAX-ACCESS 		read-write
		STATUS 			current
		DESCRIPTION		"AI - mode (0: 0-10 V, 1: 4-20mA, 2: 0-20mA, 4: 4-20mA burnout)"
		::= { aiEntry 3 }

aiValue OBJECT-TYPE
		SYNTAX 			Integer32(0..65535)
		MAX-ACCESS 		read-only
		STATUS 			current
		DESCRIPTION		"AI - raw value"
		::= { aiEntry 4 }
		
aiMin OBJECT-TYPE
		SYNTAX 			Integer32(0..65535)
		MAX-ACCESS 		read-only
		STATUS 			current
		DESCRIPTION		"AI - minimum raw value"
		::= { aiEntry 5 }
		
aiMax OBJECT-TYPE
		SYNTAX 			Integer32(0..65535)
		MAX-ACCESS 		read-only
		STATUS 			current
		DESCRIPTION		"AI - maximum raw value"
		::= { aiEntry 6 }

aiValueScaled OBJECT-TYPE
		SYNTAX 			OCTET STRING
		MAX-ACCESS 		read-only
		STATUS 			current
		DESCRIPTION		"AI - scaled value"
		::= { aiEntry 7 } 
		
aiValueScaledMin OBJECT-TYPE
		SYNTAX 			OCTET STRING
		MAX-ACCESS 		read-only
		STATUS 			current
		DESCRIPTION		"AI - minimum scaled value"
		::= { aiEntry 8 }

aiValueScaledMax OBJECT-TYPE
		SYNTAX 			OCTET STRING
		MAX-ACCESS 		read-only
		STATUS 			current
		DESCRIPTION		"AI - maximum scaled value"
		::= { aiEntry 9 } 		

aiResetMinValue OBJECT-TYPE
		SYNTAX 			Integer32(0..1)
		MAX-ACCESS 		read-write
		STATUS 			current
		DESCRIPTION		"AI - reset minimum value (1: RESET)"
		::= { aiEntry 10 }

aiResetMaxValue OBJECT-TYPE
		SYNTAX 			Integer32(0..1)
		MAX-ACCESS 		read-write
		STATUS 			current
		DESCRIPTION		"AI - reset maximum value (1: RESET)"
		::= { aiEntry 11 }
		
aiStatus OBJECT-TYPE
		SYNTAX 			Integer32(0..3)
		MAX-ACCESS 		read-only
		STATUS 			current
		DESCRIPTION		"AI - status (0: normal, 1: burnout, 2: over range, 3. under range)"
		::= { aiEntry 12 }
	
aiBurnoutValue OBJECT-TYPE
		SYNTAX 			OCTET STRING
		MAX-ACCESS 		read-only
		STATUS 			current
		DESCRIPTION		"AI - burnout value"
		::= { aiEntry 13 }		

---------------------------------------------------------------
-- DI TRAP
-- 1.3.6.1.4.1.8691.10.1242.20
    diTrap OBJECT IDENTIFIER ::= { e1242 20 }

----------------------------------------------------------------    
diTrap0 NOTIFICATION-TYPE
		STATUS current
    	DESCRIPTION     "DI-00 - DI mode - status (0: OFF, 1: ON)"
        ::= { diTrap 1 }

diTrap1 NOTIFICATION-TYPE
		STATUS current
    	DESCRIPTION     "DI-01 - DI mode - status (0: OFF, 1: ON)"
        ::= { diTrap 2 }  
        
diTrap2 NOTIFICATION-TYPE
		STATUS current
    	DESCRIPTION     "DI-02 - DI mode - status (0: OFF, 1: ON)"
        ::= { diTrap 3 }

diTrap3 NOTIFICATION-TYPE
		STATUS current
    	DESCRIPTION     "DI-03 - DI mode - status (0: OFF, 1: ON)"
        ::= { diTrap 4 }  
        
diTrap4 NOTIFICATION-TYPE
		STATUS current
    	DESCRIPTION     "DIO-00 - DI mode - DI mode - status (0: OFF, 1: ON)"
        ::= { diTrap 5 }

diTrap5 NOTIFICATION-TYPE
		STATUS current
    	DESCRIPTION     "DIO-01 - DI mode - DI mode - status (0: OFF, 1: ON)"
        ::= { diTrap 6 }
        
diTrap6 NOTIFICATION-TYPE
		STATUS current
    	DESCRIPTION     "DIO-02 - DI mode - DI mode - status (0: OFF, 1: ON)"
        ::= { diTrap 7 }

diTrap7 NOTIFICATION-TYPE
		STATUS current
    	DESCRIPTION     "DIO-03 - DI mode - DI mode - status (0: OFF, 1: ON)"
        ::= { diTrap 8 }

----------------------------------------------------------------
-- DO TRAP
-- 1.3.6.1.4.1.8691.10.1242.21
    doTrap OBJECT IDENTIFIER ::= { e1242 21 }
----------------------------------------------------------------
doTrap0 NOTIFICATION-TYPE
		STATUS current
		DESCRIPTION 	"DIO-00 - DO mode - DO mode - status (0: OFF, 1: ON)"
        ::= { doTrap 1 }

doTrap1 NOTIFICATION-TYPE
		STATUS current
		DESCRIPTION 	"DIO-01 - DO mode - DO mode - status (0: OFF, 1: ON)"
        ::= { doTrap 2 }

doTrap2 NOTIFICATION-TYPE
		STATUS current
		DESCRIPTION 	"DIO-02 - DO mode - DO mode - status (0: OFF, 1: ON)"
        ::= { doTrap 3 }

doTrap3 NOTIFICATION-TYPE
		STATUS current
		DESCRIPTION 	"DIO-03 - DO mode - DO mode - status (0: OFF, 1: ON)"
        ::= { doTrap 4 }

----------------------------------------------------------------
-- AI TRAP Greater
-- 1.3.6.1.4.1.8691.10.1242.22
    aiTrapGreater OBJECT IDENTIFIER ::= { e1242 22 }

----------------------------------------------------------------
aiTrapG0 NOTIFICATION-TYPE
		STATUS current
		DESCRIPTION 		"AI-00 - raw value greater than threshold"
        ::= { aiTrapGreater 1 }

aiTrapG1 NOTIFICATION-TYPE
		STATUS current
		DESCRIPTION 		"AI-01 - raw value greater than threshold"
        ::= { aiTrapGreater 2 }

aiTrapG2 NOTIFICATION-TYPE
		STATUS current
		DESCRIPTION 		"AI-02 - raw value greater than threshold"
        ::= { aiTrapGreater 3 }

aiTrapG3 NOTIFICATION-TYPE
		STATUS current
		DESCRIPTION 		"AI-03 - raw value greater than threshold"
        ::= { aiTrapGreater 4 }

----------------------------------------------------------------
-- AI TRAP Smaller
-- 1.3.6.1.4.1.8691.10.1242.23
    aiTrapSmaller OBJECT IDENTIFIER ::= { e1242 23 }

----------------------------------------------------------------
aiTrapS0 NOTIFICATION-TYPE
		STATUS current
		DESCRIPTION 		"AI-00 - raw value smaller than threshold"
        ::= { aiTrapSmaller 1 }

aiTrapS1 NOTIFICATION-TYPE
		STATUS current
		DESCRIPTION 		"AI-01 - raw value smaller than threshold"
        ::= { aiTrapSmaller 2 }
        
aiTrapS2 NOTIFICATION-TYPE
		STATUS current
		DESCRIPTION 		"AI-02 - raw value smaller than threshold"
        ::= { aiTrapSmaller 3 }
        
aiTrapS3 NOTIFICATION-TYPE
		STATUS current
		DESCRIPTION 		"AI-03 - raw value smaller than threshold"
        ::= { aiTrapSmaller 4 }



----------------------------------------------------------------
-- Message TRAP
-- 1.3.6.1.4.1.8691.10.1242.30
	messageTrap OBJECT IDENTIFIER ::= { e1242 30 }

----------------------------------------------------------------
activeMessageTrap NOTIFICATION-TYPE
		STATUS current
		DESCRIPTION 	"The SNMP trap with active message"
        ::= { messageTrap 1 }

END
